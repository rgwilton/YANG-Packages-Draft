module ietf-yang-package-types {
  yang-version 1.1;
  namespace "urn:ietf:params:xml:ns:yang:ietf-yang-package-types";
  prefix "pkg-types";

  import ietf-yang-revisions {
    prefix rev;
    reference "XXXX: Updated YANG Module Revision Handling";
  }

  import ietf-yang-types {
    prefix yang;
    reference "RFC 6991: Common YANG Data Types.";
  }

  import ietf-inet-types {
    prefix inet;
    reference "RFC 6991: Common YANG Data Types.";
  }

  import ietf-yang-library {
    prefix yanglib;
    reference "RFC 8525: YANG Library";
  }

  import ietf-module-tags {
    prefix tags;
    reference
      "XXX, (draft-ietf-netmod-module-tags-03): YANG Module Tags";
  }

  organization
    "IETF NETMOD (Network Modeling) Working Group";

  contact
    "WG Web:   <http://tools.ietf.org/wg/netmod/>
     WG List:  <mailto:netmod@ietf.org>

     Author:   Rob Wilton
               <mailto:rwilton@cisco.com>";

  description
    "This module provides type and grouping definitions for YANG
     packages.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX with actual RFC number and remove this
  // note.
  revision 2019-09-11 {
    rev:revision-label 0.1.0;
    description
      "Initial revision";
    reference
      "RFC XXXX: YANG Packages.";
  }

  /*
   * Typedefs
   */

  typedef scoped-feature {
    type string {
      pattern '[a-zA-Z_][a-zA-Z0-9\-_.]*:[a-zA-Z_][a-zA-Z0-9\-_.]*';
    }
    description
      "Represents a feature name scoped to a particular module,
       identified as the '<module-name>:<feature-name>', where both
       <module-name> and <feature-name> are YANG identifier strings,
       as defiend by Section 12 or RFC 6020.";
    reference
      "RFC XXXX, YANG Packages.";
  }

  /*
   * Groupings
   */

  grouping yang-pkg-identification-leafs {
    description
      "Parameters for identifying a specific version of a YANG
       package";

    leaf name {
      type yang:yang-identifier;
      mandatory true;
      description
        "The YANG package name.";
    }
    
    leaf version {
      type rev:revision-label;
      mandatory true;
      description
        "Uniquely identies a particular version of a YANG package.

         Follows the definition for revision labels defined in
         draft-verdt-nemod-yang-module-versioning, section XXX";
    }
  }

  grouping yang-pkg-common-leafs {
    description
      "Defines definitions common to all YANG package definitions.";

    leaf timestamp {
      type yang:date-and-time;

      description
        "An optional timestamp for when this package was created.
         This does not need to be unique across all versions of a
         package.";
    }

    leaf organization {
      type string;

      description "Organization responsible for this package";
    }

    leaf contact {
      type string;

      description
        "Contact information for the person or organization to whom
         queries concerning this package should be sent.";
    }

    leaf description {
      type string;

      description "Provides a description of the package";
    }

    leaf reference {
      type string;

      description "Allows for a reference for the package";
    }

    leaf referentially-complete {
      type boolean;
      default true;
      description
        "Indicates whether the schema defined by this package is
         referentially complete.  I.e. all module imports can be
         resolved to a module explcitly defined in this package or
         one of the imported packages.";
    }

    leaf is-local {
      type boolean;
      default false;
      description
        "Defines that the package definition is local to the server,
         and the name of the package MAY not be unique, and the
         package definition MAY not be available in an offline file.

         Local packages can be used when the schema for the device
         can be changed at runtime through the addition or removal of
         software packages, or hot fixes.";
    }
    
    leaf previous-version {
      type rev:revision-label;
      description
        "The previous package version that this version has been
         derived from.  This leaf allows a full version history graph
         to be constructed if required.";
    }

    leaf nbc-changes {
      type boolean;
      default false;
      description
        "Indicates whether the defined package version contains
         non-backwards-compatible changes relative to the package
         version defined in the 'previous-version' leaf.";
    }

    leaf-list tag {
      type tags:tag;
      description
        "Tags associated with a YANG package.  Module tags defined in
         XXX, ietf-netmod-module-tags can be used here but with the
         modification that the tag applies to the entire package
         rather than a specific module.  See the IANA 'YANG Module
         Tag Prefix' registry for reserved prefixes and the IANA
         'YANG Module IETF Tag' registry for IETF standard tags.";
    }

    leaf-list supported-feature {
      type scoped-feature;
      description
        "List all features from all modules included in the package
         (either directly, or via other package imports) that MUST be
         supported by any server implementing the package.  All other
         features defined in included modules are OPTIONAL to
         implement.

         Features are identified using <module-name>:<feature-name>";
    }

    list imported-packages {
      key "name version";
      description
        "An entry in this list represents a package that is imported
         as part of the package definition, or an indirectly imported
         package that is changed in a non backwards compatible way.

         It is also used to excplictly resolve conflicting package
         imports from imported packages by choosing which 

         If imported packages implement different revisions or
         versions of the same module, then an explicit entry in the
         module list MUST be provided to select the specific module
         version 'implemented' by this package definition.

         If the schema for any packages that are imported either
         directly, or indirectly via another package import are
         changed in a non-backwards-compatible way then they MUST be
         explicitly listed in the imported-packages list with the
         'modified' leaf set to true.

         For import-only modules, the replaces-revision leaf-list can
         be used to select the specific module versions imported by
         this package.";
      reference
        "XXX";

      uses yang-pkg-identification-leafs;

      leaf-list replaces-version {
        type rev:revision-label;
        description
          "Gives the version of an imported package version that
           is replaced by this package import revision.";
      }

      leaf modified {
        type boolean;
        default false;
        description
          "Set to true if any data nodes in this package are modified
           in a non backwards compatible way, either through the use
           of deviations, or because one of the modules has been
           replaced by an earlier module version.";
      }

      leaf-list location {
        type inet:uri;
        description
          "Contains a URL that represents where an instance data file
           for this YANG package can be found.

           This leaf will only be present if there is a URL available
           for retrieval of the schema for this entry.

           If multiple locations are provided, then the first
           location in the leaf-list MUST be the definitive location
           that uniquely identifies this package";
      }

      leaf checksum {
        type string {
          length "64..64";
          pattern "[0-9a-fA-F]*";
        }
        description 
          "The SHA-256 hash calculated on the textual package
           definition, represented as a hexadecimal string.";
      }
    }
  }

  grouping yang-pkg-file-definition {
    description
      "The set of parameters that describe a particular YANG
       package.";

    uses yang-pkg-identification-leafs;
    
    uses yang-pkg-common-leafs;

    list module {
      key "name";
      description
        "An entry in this list represents a module that must be
         implemented by a server implementing this package, as per
         RFC 7950 section 5.6.5, with a particular set of supported
         features and deviations.

         A entry in this list overrides any module version
         'implemented' by an imported package";
      reference
        "RFC 7950: The YANG 1.1 Data Modeling Language.";

      leaf name {
        type yang:yang-identifier;
        mandatory true;
        description
          "The YANG module name.";
      }

      leaf revision {
        type rev:revision-date-or-label;
        description
          "The YANG module revision date or revision-label.

           If no revision statement is present in the YANG module,
           this leaf is not instantiated.";
      }

      leaf namespace {
        type inet:uri;
        description
          "The XML namespace identifier for this module.";
      }

      uses yanglib:location-leaf-list;

      leaf checksum {
        type string {
          length "64..64";
          pattern "[0-9a-fA-F]*";
        }
        description 
          "The SHA-256 hash calculated on the textual module
           definition, represented as a hexadecimal string.";
      }

      list submodule {
        key "name";
        description
          "Each entry represents one submodule within the
           parent module.";

        leaf name {
          type yang:yang-identifier;
          description
            "The YANG submodule name.";
        }
        leaf revision {
          type yanglib:revision-identifier;
          mandatory true;
          description
            "The YANG submodule revision date.  If the parent module
             include statement for this submodule includes a revision
             date then it MUST match this leaf's value.";
        }

        uses yanglib:location-leaf-list;

        leaf checksum {
          type string {
            length "64..64";
            pattern "[0-9a-fA-F]*";
          }
          description 
            "The SHA-256 hash calculated on the textual submodule
             definition, represented as a hexadecimal string.";
        }
      }
    }

    list import-only-module {
      key "name revision";
      description
        "An entry in this list indicates that the server imports
         reusable definitions from the specified revision of the
         module, but does not implement any protocol accessible
         objects from this revision.

         Multiple entries for the same module name MAY exist.  This
         can occur if multiple modules import the same module, but
         specify different revision-dates in the import statements.";

      leaf name {
        type yang:yang-identifier;
        description
          "The YANG module name.";
      }

      leaf revision {
        type rev:revision-date-or-label;
        description
          "The YANG module revision date or revision-label.

           If no revision statement is present in the YANG module,
           this leaf is not instantiated.";
      }

      leaf-list replaces-revision {
        type rev:revision-date-or-label;
        description
          "Gives the revision of an import-only-module defined in
           an imported package that is replaced by this
           import-only-module revision.";
      }

      leaf namespace {
        type inet:uri;
        description
          "The XML namespace identifier for this module.";
      }

      uses yanglib:location-leaf-list;

      leaf checksum {
        type string {
          length "64..64";
          pattern "[0-9a-fA-F]*";
        }
        description 
          "The SHA-256 hash calculated on the textual submodule
           definition, represented as a hexadecimal string.";
        }

      list submodule {
        key "name";
        description
          "Each entry represents one submodule within the
           parent module.";

        leaf name {
          type yang:yang-identifier;
          description
            "The YANG submodule name.";
        }
        leaf revision {
          type yanglib:revision-identifier;
          mandatory true;
          description
            "The YANG submodule revision date.  If the parent module
             include statement for this submodule includes a revision
             date then it MUST match this leaf's value.";
        }

        uses yanglib:location-leaf-list;

        leaf checksum {
          type string {
            length "64..64";
            pattern "[0-9a-fA-F]*";
          }
          description 
            "The SHA-256 hash calculated on the textual submodule
             definition, represented as a hexadecimal string.";
        }
      }
    }
  }

  grouping yang-pkg-library-definition {
    description
      "The set of parameters that describe a particular YANG
       package.";

    uses yang-pkg-identification-leafs;
    uses yang-pkg-common-leafs;
    
    leaf-list module-set {
      type leafref {
        path "/yanglib:yang-library/yanglib:module-set/yanglib:name";
      }
      description
        "Describes any modules in addition to, and replacing, and
         modules defined in the imported packages.

         If a non import-only module appears in multiple module sets,
         then the module revision and the associated features and
         deviations must be identical.";
    }

    leaf-list location {
      type inet:uri;
      description
        "Contains a URL that represents where an instance data file
         for this YANG package can be found.

         This leaf will only be present if there is a URL
         available for retrieval of the schema for this entry.

         If multiple locations are provided, then the first location
         in the leaf-list MUST be the definitive location that
         uniquely identifies this package";
    }

    leaf checksum {
      type string {
        length "64..64";
        pattern "[0-9a-fA-F]*";
      }
      description 
        "The SHA-256 hash calculated on the textual package
         definition, represented as a hexadecimal string.";
    }
  } 
}
