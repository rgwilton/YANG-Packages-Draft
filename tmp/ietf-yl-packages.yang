module ietf-yl-packages {
  yang-version 1.1;
  namespace "urn:ietf:params:xml:ns:yang:ietf-yl-packages";
  prefix pkg;

  import ietf-yang-revisions {
    prefix rev;
    reference "XXXX: Updated YANG Module Revision Handling";
  }

  import ietf-yang-package-types {
    prefix pkg-types;
    reference "RFC XXX: YANG Packages.";
  }

  import ietf-yang-library {
    prefix yanglib;
    reference "RFC 7895bis: YANG Library";
  }

  organization
    "IETF NETMOD (Network Modeling) Working Group";

  contact
    "WG Web:   <http://tools.ietf.org/wg/netmod/>
     WG List:  <mailto:netmod@ietf.org>

     Author:   Rob Wilton
               <mailto:rwilton@cisco.com>";

  description
    "This module provides defined augmentations to YANG library to 
     allow a server to report YANG package information.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: update the date below with the date of RFC publication
  // and remove this note.
  // RFC Ed.: replace XXXX with actual RFC number and remove this
  // note.
  revision 2019-09-11 {
    rev:revision-label 0.1.0;
    description
      "Initial revision";
    reference
      "RFC XXXX: YANG Schema Versioning.";
  }


  /*
   * Add the list of packages into YANG libary.
   */
  augment "/yanglib:yang-library" {
    description "Add YANG package definitions into YANG library";
    
    list package {
      key "name version";
      config "false";

      description "Defines the packages available on this server.";

      uses "pkg-types:yang-pkg-library-definition";
    }
  }

  /*
   * Allow schema to be related to a YANG package.
   */
  augment "/yanglib:yang-library/yanglib:schema" {
    description
      "Allow datastore schema to be related to a YANG package";
    
    container package {
       leaf name {
         type leafref {
           path "/yanglib:yang-library/package/name";
         }
         description
           "The name of the package this schema relates to.";
       }
       leaf version {
         type leafref {
           path '/yanglib:yang-library/'
             + 'package[name = current()/../name]/version';
         }

         description
           "The version of the package this schema relates to.";
       }
       leaf-list supported-feature {
         type pkg-types:scoped-feature;
         description
           "Lists all supported features from all supported modules
            included in the package.

            Reports the same information that is available via the
            'feature' leaf list in YANG library, and is provided as a
            convenience to clients to avoid having to query the full
            YANG library information.

            Features are identified using 
            '<module-name>:<feature-name>'";
       }
       
      description
        "Describes which package the schema directly relates to, if
         any.";
    }
  }

  /*
   * Allow import-only modules to list the versions that they are
   * replacing.
   */
    
  augment
    "/yanglib:yang-library/yanglib:module-set/" +
    "yanglib:import-only-module" {

    description
      "Add replaces-revision to import-only-module definitions";

    leaf-list replaces-revision {
      type rev:revision-date-or-label;
      description
        "Gives the revision of an import-only-module defined in an
         imported package that is replaced by this import-only-module
         revision.

         Only used for YANG package definitions";
    }
  }
}
